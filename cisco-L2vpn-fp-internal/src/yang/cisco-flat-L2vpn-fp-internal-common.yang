module cisco-flat-L2vpn-fp-internal-common {
  namespace "http://cisco.com/ns/nso/cfp/cisco-flat-L2vpn-fp-internal-common";
  prefix cisco-flat-L2vpn-fp-internal-common;

  import tailf-common {
    prefix tailf;
  }
  import tailf-ncs {
    prefix ncs;
  }

  description "L2vpn Common module";

  revision 2025-09-23 {
    description "Modified default value for iosxr-default-ned-id to cisco-iosxr-cli-7.70";
  }

  revision 2025-08-22 {
    description "Added : added the status of Self Test(self-test) action as deprecated";
  }
  
  revision 2025-06-19 {
    description "Modified default value for iosxr-default-ned-id to cisco-iosxr-cli-7.69";
  }

  revision 2025-05-12 {
    description "Modified default value for iosxr-default-ned-id to cisco-iosxr-cli-7.67";
  }

  revision 2025-04-17 {
    description "Modified default value for iosxr-default-ned-id to cisco-iosxr-cli-7.66";
  }

  revision 2025-03-26 {
    description "Modified default value for iosxr-default-ned-id to cisco-iosxr-cli-7.62";
  }

  revision 2024-12-02 {
    description "Modified default value for iosxr-default-ned-id to cisco-iosxr-cli-7.61";
  }

  revision 2024-10-09 {
    description "Modified default value for iosxr-default-ned-id to cisco-iosxr-cli-7.58";
  }

  revision 2024-10-03 {
    description
       "Added container match-etag-set under route-policy -> statements -> statement -> conditions
        Added leaf co-flag under route-policy -> statements -> statement -> actions -> bgp-actions -> set-ext-community
        Modified container attach-point under grouping sr-te-grp -> odn by adding leaf route-policy-type";
  }

  revision 2023-10-04 {
    description "Modified default value for iosxr-default-ned-id to cisco-iosxr-cli-7.52";
  }

  revision 2023-05-30 {
    description "Removed policy-result leaf under route-policy -> statements -> statement -> actions";
  }

  revision 2023-05-04 {
    description "Modified default value for iosxr-default-ned-id to cisco-iosxr-cli-7.49";
  }

  revision 2023-04-20 {
    description "Modified default value for iosxr-default-ned-id to cisco-iosxr-cli-7.48";
  }

  revision 2023-03-13 {
    description
      "Modified: tailf:info and description under ethernet-y-1731-grouping -> ethernet-service-oam -> md-level
       Modified: tailf:info and description under ethernet-y-1731-grouping -> ethernet-service-oam -> y-1731 -> type -> icc-based
       Modified: tailf:info and description under ethernet-y-1731-grouping -> ethernet-service-oam -> y-1731 -> type -> number
       Modified: tailf:info and description under ethernet-y-1731-grouping -> ethernet-service-oam -> y-1731 -> y-1731-profile -> probe -> burst -> message-count
       Modified: tailf:info and description under ethernet-y-1731-grouping -> ethernet-service-oam -> y-1731 -> y-1731-profile -> probe -> burst -> message-period
       Modified: tailf:info and description under ethernet-y-1731-grouping -> ethernet-service-oam -> y-1731 -> y-1731-profile -> probe -> measurement-interval
       Modified: tailf:info and description under ethernet-y-1731-grouping -> ethernet-service-oam -> y-1731 -> y-1731-profile -> probe -> frame-size
       Modified: tailf:info and description under ethernet-y-1731-grouping -> ethernet-service-oam -> y-1731 -> y-1731-profile -> probe -> priority
       Modified: tailf:info and description under ethernet-y-1731-grouping -> ethernet-service-oam -> y-1731 -> y-1731-profile -> delay-params -> statistic -> cos
       Modified: tailf:info and description under ethernet-y-1731-grouping -> ethernet-service-oam -> y-1731 -> y-1731-profile -> loss-params -> statistic -> cos
       Modified: tailf:info and description under ethernet-y-1731-grouping -> ethernet-service-oam -> y-1731 -> y-1731-profile -> schedule -> interval
       Modified: tailf:info and description under ethernet-y-1731-grouping -> ethernet-service-oam -> y-1731 -> y-1731-profile -> schedule -> duration
       Modified: tailf:info and description under ethernet-y-1731-grouping -> ethernet-service-oam -> y-1731 -> y-1731-profile -> bucket-details -> bucket-size
       Modified: tailf:info and description under ethernet-y-1731-grouping -> ethernet-service-oam -> y-1731 -> y-1731-profile -> bucket-details -> bucket-archive
       Modified: tailf:info and description under route-policy -> statements -> statement -> conditions -> match-evpn-route-type-set -> evpn-route-type";
  }
  
  revision 2023-03-07 {
    description "Removed: all when, must conditions and mandatory checks";
  }

  revision 2023-03-02 {
    description "Modified default value for iosxr-default-ned-id to cisco-iosxr-cli-7.46";
  }

  revision 2023-02-08 {
    description "Modified default value for iosxr-default-ned-id to cisco-iosxr-cli-7.45";
  }

  revision 2023-01-23 {
    description "Modified default value for iosxr-default-ned-id to cisco-iosxr-cli-7.44";
  }

  revision 2022-12-07 {
    description "Modified default value for iosxr-default-ned-id to cisco-iosxr-cli-7.43";
  }

  revision 2022-11-03 {
    description
      "Removed: 'mode' under route-policy -> statements -> statement -> conditions -> match-rd-set.
       Modified: description/tailf:info for route-policy -> statements -> statement -> conditions -> match-rd-set.
       Modified: description/tailf:info for route-policy -> statements -> statement -> conditions -> match-evpn-route-type-set.";
  }

  revision 2022-10-23 {
    description
      "Modified: list local-route-policy to leaf-list local-route-policy
       Added: grouping sr-te-grp, sr-te-pref-path-grp, sr-te-odn-grp, l2vpn-routing-policy-grp";
  }

  revision 2022-09-13 {
    description "Modified default value for iosxr-default-ned-id to cisco-iosxr-cli-7.42";
  }

  revision 2022-08-22 {
    description
      "Added: 'manual' under l2vpn-rr-parent-route-policy -> local-route-policy
       Added: grouping qos";
  }

  revision 2022-08-19 {
    description "Modified default value for iosxr-default-ned-id to cisco-iosxr-cli-7.41";
  }

  revision 2022-08-09 {
    description "Modified default value for iosxr-default-ned-id to cisco-iosxr-cli-7.40";
  }

  revision 2022-06-13 {
    description
      "Modified: pattern under srv6 -> locator -> type";
  }

  revision 2022-05-04 {
    description "Modified default value for iosxr-default-ned-id to cisco-iosxr-cli-7.39";
  }

  revision 2022-04-15 {
    description
      "Modified: description under srv6 -> locator
       Added: pattern under srv6 -> locator -> type";
  }

  revision 2022-03-30 {
    description
      "Removed: evpn-route-type under l2vpn-rr-parent-route-policy -> local-route-policy
       Added: prefix under l2vpn-rr-parent-route-policy -> local-route-policy";
  }

  revision 2022-02-15 {
    description
      "Added: evpn-route-type under l2vpn-rr-parent-route-policy -> local-route-policy
       Added: site-only under flat-L2vpn-internal-actions -> cleanup -> input -> site-type";
  }

  revision 2022-01-13 {
    description "Modified default value for iosxr-default-ned-id to cisco-iosxr-cli-7.38";
  }

  revision 2022-01-13 {
    description
      "Added: grouping srv6-grp";
  }

  revision 2021-12-03 {
	description
	  "Removed: core-fp-common reference";
  }

  revision 2021-11-17 {
    description
      "Removed: must condition under y-1731-profile -> probe -> burst -> message-period
       Removed: 'default 60' for y-1731-profile -> schedule -> duration
       Removed: 'default 60' for y-1731-profile -> probe -> measurement-interval
       Modified: default under cfp-configurations -> iosxr-default-ned-id
       Modified: Changed to type union for y-1731-profile -> probe -> measurement-interval";
  }

  revision 2021-09-14 {
    description
      "Modified: description/tailf:info for y-1731-profile -> message-period
       Modified: range for leaf interval in grouping ethernet-y-1731-grouping
                 -> y-1731 -> y-1731-profile -> schedule";
  }

  revision 2021-08-31 {
    description
      "Added: ethernet-y-1731-grouping -> y-1731 -> type choice (icc-based|number)";
  }

  revision 2021-08-27 {
    description
      "Added: container probe in list y-1731-profile
       Added: leaf message-count in y-1731-profile -> probe
       Moved: y-1731-profile -> measurment-internal to y-1731-profile -> probe -> measurement-interval
       Moved: y-1731-profile -> message-period to y-1731-profile -> probe -> burst -> message-period
       Moved: y-1731-profile -> frame-size to y-1731-profile -> probe -> frame-size
       Moved: y-1731-profile -> priority to y-1731-profile -> probe -> priority
       Added: container schedule in grouping ethernet-y-1731-grouping -> y-1731 -> y-1731-profile
       Added: leaf interval in grouping ethernet-y-1731-grouping -> y-1731 -> y-1731-profile -> schedule
       Added: leaf duration in grouping ethernet-y-1731-grouping -> y-1731 -> y-1731-profile -> schedule
       Added: container bucket-details under ethernet-y-1731-grouping -> y-1731 -> y-1731-profile";
  }

  revision 2021-06-25 {
    description
      "Added: leaf statistic-id under grouping ethernet-y-1731-grouping -> y-1731 -> y-1731-profile -> delay-params -> statistic
       Added: leaf cos under grouping ethernet-y-1731-grouping -> y-1731 -> y-1731-profile -> delay-params -> statistic
       Added: leaf delay-type under grouping ethernet-y-1731-grouping -> y-1731 -> y-1731-profile -> delay-params -> statistic
       Added: leaf statistic-id under grouping ethernet-y-1731-grouping -> y-1731 -> y-1731-profile -> loss-params -> statistic
       Added: leaf cos under grouping ethernet-y-1731-grouping -> y-1731 -> y-1731-profile -> loss-params -> statistic
       Added: enum synthetic-loss under grouping ethernet-y-1731-grouping -> y-1731 -> y-1731-profile -> type
       Added: when condition to ethernet-y-1731-grouping -> y-1731 -> y-1731-profile -> frame-size
       Removed: leaf synthetic-loss under grouping ethernet-y-1731-grouping -> y-1731 -> y-1731-profile -> loss-params";
  }

  revision 2021-05-28 {
    description
      "Added: leaf version under grouping ethernet-y-1731-grouping -> y-1731 -> y-1731-profile -> delay-params";
  }

  revision 2021-05-27 {
    description
      "Removed: leaf loss-measurement under grouping ethernet-y-1731-grouping -> y-1731 -> y-1731-profile
       Removed: leaf synthetic-loss-measurement under grouping ethernet-y-1731-grouping -> y-1731 -> y-1731-profile
       Removed: container delay-measurement under grouping ethernet-y-1731-grouping -> y-1731 -> y-1731-profile
       Added: container delay-params under grouping ethernet-y-1731-grouping -> y-1731 -> y-1731-profile
       Added: container loss-params under grouping ethernet-y-1731-grouping -> y-1731 -> y-1731-profile";
  }

  revision 2021-05-25 {
    description
      "Added: leaf priority under grouping ethernet-y-1731-grouping -> y-1731 -> y-1731-profile";
  }

  revision 2021-03-25 {
    description "Added: new ethernet-service-oam";
  }

  revision 2021-02-15 {
    description "Modified default value for iosxr-default-ned-id to cisco-iosxr-cli-7.33";
  }

  revision 2020-12-11 {
    description "Modified default value for iosxr-default-ned-id to cisco-iosxr-cli-7.32";
  }

  revision 2020-11-24 {
    description "Modified l2vpn-rr-parent-route-policy -> original-rr to original-rr-route-policy";
  }

  revision 2020-11-10 {
    description "Added leaf sync-direction as mandatory input to error-recovery action";
  }

  revision 2020-11-06 {
    description "Added: l2vpn-rr-parent-route-policy servicepoint";
  }

  typedef asn-ip-type {
    type string {
      tailf:info "ASN:nn or IPV4-address:nn,VPN Route Distinguisher";
      pattern '(([0-9]+)|((([0-9]|[1-9][0-9]|1[0-9][0-9]|2[0-4][0-9]|25[0-5])'
        +'\.){3}([0-9]|[1-9][0-9]|1[0-9][0-9]|2[0-4][0-9]|25[0-5]))):[0-9]+';
    }
  }

  // Global RR Route Policy
  list l2vpn-rr-parent-route-policy {
    tailf:hidden tsdn;
    key "name device";
    leaf name {
      type string;
      tailf:info "Parent route-reflector route policy";
      description "Parent route-reflector route policy";
    }
    leaf device {
      type leafref {
        tailf:no-leafref-check;
        path "/ncs:devices/ncs:device/ncs:name";
      }
    }

    uses ncs:service-data;
    ncs:servicepoint "l2vpn-rr-parent-route-policy";

    leaf original-rr-route-policy {
      tailf:info "Original value of parent route policy";
      description "Original value of parent route policy";
      type string;
    }

    leaf-list local-route-policy {
      tailf:info "List of SR routing policy";
      description "List of SR routing policy";
      type string;
    }
  }

  container cfp-configurations {
    tailf:hidden tsdn;
    list dynamic-device-mapping {
      tailf:info "Dynamic Device Mapping";
      description "Dynamic Device Mapping";
      key "ned-id";
      leaf ned-id {
        tailf:info "Device NED ID, eg ned:netconf";
        description "Device NED ID, eg ned:netconf";
        type string;
        tailf:cli-allow-range;
      }
      leaf python-impl-class-name {
        tailf:info "Device Python implementation class, eg module.class";
        description "Device Python implementation class, eg module.class";
        type string;
        mandatory true;
      }
    }
    leaf l2vpn-validation-enabled {
      tailf:info "If set to true, following validations are done for l2vpn service:
                  1. All the site interfaces are available on the site.";
      description "If set to true, following validations are done for l2vpn service:
                  1. All the site interfaces are available on the site.";
      type boolean;
      default true;
    }
    leaf iosxr-default-ned-id {
      tailf:info "NED ID of the default IOSXR Device.";
      description "NED ID of the default IOSXR Device.";
      tailf:hidden tsdn;
      type string;
      default "cisco-iosxr-cli-7.70:cisco-iosxr-cli-7.70";
    }
  }

  container flat-L2vpn-internal-actions {
    tailf:hidden tsdn;
    tailf:action cleanup {
      tailf:actionpoint cisco-flat-L2vpn-fp-internal-cleanup;
      tailf:info "Clean up L2vpn service configuration and operational data";
      description "Clean up L2vpn service configuration and operational data";
      input {
        leaf service {
          type string;
          mandatory true;
        }
        choice site-type {
          leaf remote-site-only {
            tailf:info "Clean up L2vpn service configuration for given remote site only";
            description "Clean up L2vpn service configuration for given remote site only";
            type leafref {
              tailf:no-leafref-check;
              path "/ncs:devices/ncs:device/ncs:name";
            }
          }
          leaf local-site-only {
            tailf:info "Clean up L2vpn service configuration for given local site only";
            description "Clean up L2vpn service configuration for given local site only";
            type leafref {
              tailf:no-leafref-check;
              path "/ncs:devices/ncs:device/ncs:name";
            }
          }
          leaf site-only {
            tailf:info "Clean up L2vpn service configuration for given site only";
            description "Clean up L2vpn service configuration for given site only";
            type string;
          }
        }
        leaf no-networking {
          type boolean;
          mandatory true;
        }
      }
      output {
        leaf success {
          type boolean;
          mandatory true;
        }
        leaf detail {
          type string;
        }
      }
    }

    tailf:action error-recovery {
      tailf:actionpoint cisco-flat-L2vpn-fp-internal-error-recovery;
      tailf:info "Action to recover a service during create/update/delete from a transient failures
                  like device connection issues once the device is reachable again.
                  For create/update failures, this action issues a sync on the device
                  & redeploys the service with reconcile option.
                  For delete failures, this action issues a sync on the device &
                  redeploys zombie services.";
      description "Action to recover a service during create/update/delete from a transient failures
                  like device connection issues once the device is reachable again.
                  For create/update failures, this action issues a sync on the device
                  & redeploys the service with reconcile option.
                  For delete failures, this action issues a sync on the device &
                  redeploys zombie services.";
      input {
        leaf service {
          type string;
          mandatory true;
        }
        leaf sync-direction {
          tailf:info "sync device with sync-from or sync-to";
          description "sync device with sync-from or sync-to";
          type enumeration {
            enum sync-from;
            enum sync-to;
          }
          mandatory true;
        }
        choice site-type {
          leaf remote-site-only {
            tailf:info "Clean up L2vpn service configuration for given remote site only";
            description "Clean up L2vpn service configuration for given remote site only";
            type leafref {
              tailf:no-leafref-check;
              path "/ncs:devices/ncs:device/ncs:name";
            }
          }
          leaf local-site-only {
            tailf:info "Clean up L2vpn service configuration for given local site only";
            description "Clean up L2vpn service configuration for given local site only";
            type leafref {
              tailf:no-leafref-check;
              path "/ncs:devices/ncs:device/ncs:name";
            }
          }
          leaf site-only {
            tailf:info "Clean up L2vpn service configuration for given site only";
            description "Clean up L2vpn service configuration for given site only";
            type string;
          }
        }
      }
      output {
        leaf success {
          type boolean;
          mandatory true;
        }
        leaf detail {
          type string;
        }
      }
    }
  }// flat-L2vpn-actions ends

  grouping action-grouping {
    container action {
      status deprecated;
      tailf:action self-test {
        tailf:actionpoint cisco-flat-L2vpn-fp-internal-self-test;
        input {
        }
        output {
          leaf status {
            type string;
          }
          leaf message {
            type string;
          }
        }
      }

    }

  }// action-grouping ends

  grouping ethernet-y-1731-grouping {
    container ethernet-service-oam {
      presence "true";
      description "Container for Ethernet service OAM.";
      tailf:info "Container for Ethernet service OAM.";

      leaf md-name {
        description "Maintenance domain name";
        tailf:info "Maintenance domain name";
        type string;
      }
      leaf md-level {
        description "<0-7> Maintenance domain level";
        tailf:info "<0-7> Maintenance domain level";
        type uint8 {
          range "0..7";
        }
      }

      list y-1731 {
        description "List for y-1731.";
        tailf:info "List for y-1731.";
        key "maid";
        leaf maid {
          type string;
          description "MA ID ";
          tailf:info "MA ID ";
        }
        leaf mep-id {
          type uint16;
          description "Local MEP ID";
          tailf:info "Local MEP ID";
        }
        leaf remote-mep-id {
          type uint16;
          description "Remote MEP ID";
          tailf:info "Remote MEP ID";
        }
        choice type {
          leaf icc-based {
            description "<0-12> icc-based SMAN ID";
            tailf:info "<0-12> icc-based SMAN ID";
            type string {
              length "0..12";
            }
          }
          leaf number {
            description "<0-65535> number SMAN ID";
            tailf:info "<0-65535> number SMAN ID";
            type uint16 {
              range "0..65535";
            }
          }
        }
        leaf message-period {
          description "Defines the interval between OAM messages. The message
                       period is expressed in 3.3ms|10ms|100ms|1s|10s|1m|10m";
          tailf:info "Defines the interval between OAM messages. The message
                      period is expressed in 3.3ms|10ms|100ms|1s|10s|1m|10m";
          type string {
            pattern '(3\.3ms|10ms|100ms|1s|10s|1m|10m)';
          }
          default '1s';
        }
        list y-1731-profile {
          description "Y-1731 profile.
                       Can be standard profile or customized profile.";
          tailf:info "Y-1731 profile.
                      Can be standard profile or customized profile.";
          key name;
          leaf name {
            type string;
          }
          leaf type {
            type enumeration {
              enum 'delay';
              enum 'loss';
              enum 'synthetic-loss';
            }
            description
             "Performance monitor types";
            tailf:info "Performance monitor types";
          }
          container probe {
            description
              "SLA Profile Probe. Only applicable to Cisco XR devices.";
            tailf:info
              "SLA Profile Probe. Only applicable to Cisco XR devices.";

            leaf type {
              description "Probe Type";
              tailf:info  "Probe Type";
              type enumeration {
                enum burst;
                enum packet;
              }
              default burst;
            }
            container burst {
              description "Burst Parameters";
              tailf:info  "Burst Parameters";

              leaf message-count {
                description
                  "<2-1200> Defines number of OAM messages sent per interval";
                tailf:info
                  "<2-1200> Defines number of OAM messages sent per interval";
                type uint16 {
                  range "2..1200";
                }
                default 60;
              }
              leaf message-period {
                type uint32 {
                  range "50..30000";
                }
                default 1000;
                description
                  "<50-30000> Defines the interval between OAM messages. The message
                    period is expressed in milliseconds";
                tailf:info  "<50-30000> Defines the interval between OAM messages. The message
                    period is expressed in milliseconds";
              }
            }
            leaf measurement-interval {
              type union {
                type uint32 {
                  range "1..3600";
                }
                type enumeration {
                  enum once;
                }
              }
              default 60;
              description
                "<1-3600> Specifies the measurement interval for statistics. The
                  measurement interval is expressed in seconds";
              tailf:info "<1-3600> Specifies the measurement interval for statistics. The
                  measurement interval is expressed in seconds";
            }
            leaf frame-size {
              type uint16 {
                range "1..9000";
              }
              default 1000;
              description
                "<1-9000> Frame size";
              tailf:info "<1-9000> Frame size";
            }
            leaf priority {
              description "<0-7> Specify the priority to use when sending OAM messages";
              tailf:info "<0-7> Specify the priority to use when sending OAM messages";
              type uint8 {
                range "0..7";
              }
            }
          }
          container delay-params {
            description
              "Delay Parameters";
            tailf:info
              "Delay Parameters";
            list statistic {
              description
                "Statistic";
              tailf:info
                "Statistic";
              key type;
              leaf type {
                description
                  "Statistics Type. Jitter type only applicable for Cisco XR devices.";
                tailf:info
                  "Statistics Type. Jitter type only applicable for Cisco XR devices.";
                type enumeration {
                  enum 'delay-two-way';
                  enum 'delay-sd';
                  enum 'delay-ds';
                  enum 'jitter-two-way';
                  enum 'jitter-sd';
                  enum 'jitter-ds';
                }
              }
              leaf statistic-id {
                tailf:info "id allocated by resource-manager id-allocator";
                description "id allocated by resource-manager id-allocator";
                type uint32 {
                  range "1..2147483647";
                }
              }
              leaf cos {
                description
                  "<0-7> Class of service. Only applicable for Cisco XE devices.";
                tailf:info
                  "<0-7> Class of service. Only applicable for Cisco XE devices.";
                type uint8 {
                  range "0..7";
                }
                default 0;
              }
            }
            leaf version {
              description
                "Delay Version";
              tailf:info
                "Delay Version";
              type enumeration {
                enum 0;
                enum 1;
              }
              default 1;
            }
            leaf delay-type {
              description
                "Delay type. Only applicable for Cisco XE devices.";
              tailf:info
                "Delay type. Only applicable for Cisco XE devices.";
              type enumeration {
                enum 'delay';
                enum 'delay-variation';
                enum 'both';
              }
              default "delay";
            }
          }
          container loss-params {
            description
              "Loss Parameters";
            tailf:info
              "Loss Parameters";
            list statistic {
              description
                "Statistic";
              tailf:info
                "Statistic";
              key type;
              leaf type {
                description
                  "Statistics Type";
                tailf:info
                  "Statistics Type";
                type enumeration {
                  enum 'loss-sd';
                  enum 'loss-ds';
                }
              }
              leaf statistic-id {
                tailf:info "id allocated by resource-manager id-allocator";
                description "id allocated by resource-manager id-allocator";
                type uint32 {
                  range "1..2147483647";
                }
              }
              leaf cos {
                description
                  "<0-7> Class of service. Only applicable for Cisco XE devices.";
                tailf:info
                  "<0-7> Class of service. Only applicable for Cisco XE devices.";
                type uint8 {
                  range "0..7";
                }
                default 0;
              }
            }
          }
          container schedule {
            description
                "Schedule Parameters";
            tailf:info
                "Schedule Parameters";

            leaf interval {
                description
                  "<1|2|3|4|5|6|8|9|10|12|15|16|18|20|24|30|32|36|40|45|48|60|80|90>
                  Interval between operations expressed in minutes. Must be a factor of 1440.
                  Only applicable for Cisco XR devices.";
                tailf:info
                  "<1|2|3|4|5|6|8|9|10|12|15|16|18|20|24|30|32|36|40|45|48|60|80|90>
                  Interval between operations expressed in minutes. Must be a factor of 1440.
                  Only applicable for Cisco XR devices.";
                type uint8 {
                  range "1|2|3|4|5|6|8|9|10|12|15|16|18|20|24|30|32|36|40|45|48|60|80|90";
                }
              default 60;
            }
            leaf duration {
              description
                "<1-1440> Duration of operations expressed in minutes.
                The 'forever' option will try to schedule infinitely if supported; otherwise,
                maximum number of allowed minutes will be used";
              tailf:info
                "<1-1440> Duration of operations expressed in minutes.
                The 'forever' option will try to schedule infinitely if supported; otherwise,
                maximum number of allowed minutes will be used";
              type union {
                type uint16 {
                  range "1..1440";
                }
                type enumeration {
                  enum forever;
                }
              }
            }
          }
          container bucket-details {
            description
              "Configuration for buckets in which statistics are collected. Only applicable for Cisco XR devices.";
            leaf bucket-size {
              description
                "<1-100> Specifies the size of each bucket.
                 The number of probes that each buckets may contain. Only applicable for Cisco XR devices.";
              tailf:info
                "<1-100> Specifies the size of each bucket.
                 The number of probes that each buckets may contain. Only applicable for Cisco XR devices.";
              type uint8 {
                range "1..100";
              }
              default 1;
            }
            leaf bucket-archive {
              description "<1-100> Number of buckets to store. Only applicable for Cisco XR devices.";
              tailf:info "<1-100> Number of buckets to store. Only applicable for Cisco XR devices.";
              type uint8 {
                range "1..100";
              }
              default 100;
            }
          }
        }
      }
    }
  }

  grouping srv6-grp {
    container srv6 {
      presence  "true";
      tailf:info "SRv6 Options";
      description "SRv6 Options";

      leaf locator {
        tailf:info "SRv6 locator name (1-58 chars) at individual evi service level,
                    leave it empty if evi or global level locator is used. Special characters are not allowed.";
        description "SRv6 locator name (1-58 chars) at individual evi service level,
                     leave it empty if evi or global level locator is used. Special characters are not allowed.";
        type string {
          pattern '[0-9a-zA-Z_]*';
          length "1..58";
        }
      }
    }
  }

  grouping sr-te-grp {
    choice type {
      case odn {
        container odn {
          tailf:info "ODN SR policy";
          description "ODN SR policy";
          presence true;
          container attach-point {
              leaf parent-rr-route-policy {
                type string {
                  length "1..max";
                }
                tailf:info "Parent RR Route Policy to apply local route policies";
                description "Parent RR Route Policy to apply local route policies";
              }
          }
          leaf route-policy-type {
            type enumeration {
              enum "import";
              enum "export";
              enum "both";
            }
          }
          uses l2vpn-routing-policy-grp;
        }
      }
      case preferred-path {
        uses sr-te-pref-path-grp;
      }
    }
  }

  grouping sr-te-pref-path-grp {
    container preferred-path {
      presence true;
      tailf:info "Specify SR TE policy for preferred path";
      description "Specify SR TE policy for preferred path";
      leaf policy {
        tailf:info "Name of SR TE policy";
        type string;
      }
      leaf fallback {
        tailf:info "Fallback option for preferred path";
        description "Fallback option for preferred path";
        type enumeration {
          enum disable {
            tailf:info "Disable fallback for preferred path";
          }
        }
      }
    }
  }

  grouping sr-te-odn-grp {
    choice type {
      case odn {
        container odn {
          tailf:info "ODN SR policy";
          description "ODN SR policy";
          presence true;

          choice attach-or-not {
            container attach-point {
              choice parent-rr-route-policy-choice {
                leaf parent-rr-route-policy {
                  type string {
                    length "1..max";
                  }
                  tailf:info "Parent RR Route Policy to apply local route policies";
                  description "Parent RR Route Policy to apply local route policies";
                }
              }
            }
            leaf route-policy-type {
              type enumeration {
                enum "import";
                enum "export";
                enum "both";
              }
            }
          }
          uses l2vpn-routing-policy-grp;
        }
      }
    }
  }

  grouping l2vpn-routing-policy-grp {
    list route-policy {
      tailf:info "List of Route Policies pushed to Device";
      description
        "List of Route Policies pushed to Device";
      key "route-policy-name";
      leaf route-policy-name {
        type string;
        tailf:info "Name of the top-level policy definition; this name
          is used in references to the current policy.";
        description
          "Name of the top-level policy definition; this name
          is used in references to the current policy.";
      }
      container statements {
        tailf:info "Enclosing container for policy statements.";
        description
          "Enclosing container for policy statements.";
        list statement {
          key "name";
          ordered-by user;
          tailf:info "Policy statements group conditions and actions
            within a policy definition.  They are evaluated in
            the order specified.";
          description
            "Policy statements group conditions and actions
            within a policy definition.  They are evaluated in
            the order specified.";
          leaf name {
            type string;
            tailf:info "Name of the policy statement.";
            description
              "Name of the policy statement.";
          }
          container conditions {
            tailf:info "Condition statements for the current policy
              statement.";
            description
              "Condition statements for the current policy
              statement.";
            container match-rd-set {
              presence "Indicates presence of match-rd set";
              leaf-list rd {
                type asn-ip-type;
                tailf:info "ASN:nn or IPV4-address:nn,VPN Route Distinguisher; List of addresses in the RD set.";
                description
                  "ASN:nn or IPV4-address:nn,VPN Route Distinguisher; List of addresses in the RD set.";
              }
              tailf:info "Match a referenced RD-set.";
              description
                "Match a referenced RD-set.";
            }
            container match-evpn-route-type-set {
              presence "Indicates presence of evpn-route-type set";
              leaf-list evpn-route-type {
                type uint8 {
                  range  "0..11";
                }
                tailf:info "<0-11> List of routes in the evpn-route-type set.";
                description
                  "<0-11> List of routes in the evpn-route-type set.";
              }
              tailf:info "Match a referenced evpn-route-type-set.";
              description
                "Match a referenced evpn-route-type-set.";
            }
            container match-etag-set {
              presence "Indicates presence of match-etag set";
              leaf-list etag {
                type string;
                tailf:info "List of ethernet tag attributes";
                description "List of ethernet tag attributes";
              }
              tailf:info "Match a referenced etag-set.";
              description
                "Match a referenced etag-set.";
            }
            leaf match-manual {
              tailf:info "Configure match conditions for route-policy manually";
              description "Configure match conditions for route-policy manually";
              type string;
            }
          }
          container actions {
            tailf:info "Top-level container for policy action
              statements.";
            description
              "Top-level container for policy action
              statements.";
            container bgp-actions {
              tailf:info "Top-level container for BGP-specific actions";
              description
                "Top-level container for BGP-specific actions";
              presence "Indicates existence of bgp-actions";
              container set-ext-community {
                tailf:info
                  "Action to set the extended community attributes of the
                    route, along with options to modify how the community is
                    modified. Extended communities may be set using an inline
                    list OR a reference to an existing defined set (but not
                    both).";
                description
                  "Action to set the extended community attributes of the
                    route, along with options to modify how the community is
                    modified. Extended communities may be set using an inline
                    list OR a reference to an existing defined set (but not
                    both).";
                presence "Indicates presence of set-ext-community action";
                leaf tag-value {
                  type string;
                  tailf:info "Value of the tag set member.";
                  description
                    "Value of the tag set member.";
                }
                leaf co-flag {
                  type string;
                  tailf:info "co-flag value of the tag set member.";
                  description "co-flag value of the tag set member.";
                }
              }
            }
          }
        }
      }
    }
  }

  grouping qos {
    container qos {
      presence "true";
      tailf:info "QoS Configuration";
      description "QoS Configuration";

      leaf input-policy {
        tailf:info "Ingress Policy";
        description "Ingress Policy";
        type string;
      }
      leaf output-policy {
        tailf:info "Egress Policy";
        description "Egress Policy";
        type string;
      }
    }
  }
}
